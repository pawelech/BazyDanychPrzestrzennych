FME workspace shapefile_geotiff2postgis_raster.fmw

Parameters:
- SourceDataset_SHAPEFILE = C:\Users\pawel\Downloads\bdline_essh_gb\Data\GB\scotland_and_wales_region.shp   # Source Esri Shapefile(s)
- SourceDataset_GEOTIFF = ""C:\Users\pawel\Downloads\ras250_gb\ras250_gb\data\SX.tif" "C:\Users\pawel\Downloads\ras250_gb\ras250_gb\data\SY.tif" "C:\Users\pawel\Downloads\ras250_gb\ras250_gb\data\SZ.tif" "C:\Users\pawel\Downloads\ras250_gb\ras250_gb\data\TA.tif" "C:\Users\pawel\Downloads\ras250_gb\ras250_gb\data\TF.tif" "C:\Users\pawel\Downloads\ras250_gb\ras250_gb\data\TG.tif" "C:\Users\pawel\Downloads\ras250_gb\ras250_gb\data\TL.tif" "C:\Users\pawel\Downloads\ras250_gb\ras250_gb\data\TM.tif" "C:\Users\pawel\Downloads\ras250_gb\ras250_gb\data\TQ.tif" "C:\Users\pawel\Downloads\ras250_gb\ras250_gb\data\TR.tif" "C:\Users\pawel\Downloads\ras250_gb\ras250_gb\data\TV.tif" "C:\Users\pawel\Downloads\ras250_gb\ras250_gb\data\OV.tif" "C:\Users\pawel\Downloads\ras250_gb\ras250_gb\data\SC.tif" "C:\Users\pawel\Downloads\ras250_gb\ras250_gb\data\SD.tif" "C:\Users\pawel\Downloads\ras250_gb\ras250_gb\data\SE.tif" "C:\Users\pawel\Downloads\ras250_gb\ras250_gb\data\SH.tif" "C:\Users\pawel\Downloads\ras250_gb\ras250_gb\data\SJ.tif" "C:\Users\pawel\Downloads\ras250_gb\ras250_gb\data\SK.tif" "C:\Users\pawel\Downloads\ras250_gb\ras250_gb\data\SM.tif" "C:\Users\pawel\Downloads\ras250_gb\ras250_gb\data\SN.tif" "C:\Users\pawel\Downloads\ras250_gb\ras250_gb\data\SO.tif" "C:\Users\pawel\Downloads\ras250_gb\ras250_gb\data\SP.tif" "C:\Users\pawel\Downloads\ras250_gb\ras250_gb\data\SR.tif" "C:\Users\pawel\Downloads\ras250_gb\ras250_gb\data\SS.tif" "C:\Users\pawel\Downloads\ras250_gb\ras250_gb\data\ST.tif" "C:\Users\pawel\Downloads\ras250_gb\ras250_gb\data\SU.tif" "C:\Users\pawel\Downloads\ras250_gb\ras250_gb\data\SV.tif" "C:\Users\pawel\Downloads\ras250_gb\ras250_gb\data\SW.tif" "C:\Users\pawel\Downloads\ras250_gb\ras250_gb\data\NF.tif" "C:\Users\pawel\Downloads\ras250_gb\ras250_gb\data\NG.tif" "C:\Users\pawel\Downloads\ras250_gb\ras250_gb\data\NH.tif" "C:\Users\pawel\Downloads\ras250_gb\ras250_gb\data\NJ.tif" "C:\Users\pawel\Downloads\ras250_gb\ras250_gb\data\NK.tif" "C:\Users\pawel\Downloads\ras250_gb\ras250_gb\data\NL.tif" "C:\Users\pawel\Downloads\ras250_gb\ras250_gb\data\NM.tif" "C:\Users\pawel\Downloads\ras250_gb\ras250_gb\data\NN.tif" "C:\Users\pawel\Downloads\ras250_gb\ras250_gb\data\NO.tif" "C:\Users\pawel\Downloads\ras250_gb\ras250_gb\data\NR.tif" "C:\Users\pawel\Downloads\ras250_gb\ras250_gb\data\NS.tif" "C:\Users\pawel\Downloads\ras250_gb\ras250_gb\data\NT.tif" "C:\Users\pawel\Downloads\ras250_gb\ras250_gb\data\NU.tif" "C:\Users\pawel\Downloads\ras250_gb\ras250_gb\data\NW.tif" "C:\Users\pawel\Downloads\ras250_gb\ras250_gb\data\NX.tif" "C:\Users\pawel\Downloads\ras250_gb\ras250_gb\data\NY.tif" "C:\Users\pawel\Downloads\ras250_gb\ras250_gb\data\NZ.tif" "C:\Users\pawel\Downloads\ras250_gb\ras250_gb\data\HP.tif" "C:\Users\pawel\Downloads\ras250_gb\ras250_gb\data\HT.tif" "C:\Users\pawel\Downloads\ras250_gb\ras250_gb\data\HU.tif" "C:\Users\pawel\Downloads\ras250_gb\ras250_gb\data\HW.tif" "C:\Users\pawel\Downloads\ras250_gb\ras250_gb\data\HX.tif" "C:\Users\pawel\Downloads\ras250_gb\ras250_gb\data\HY.tif" "C:\Users\pawel\Downloads\ras250_gb\ras250_gb\data\HZ.tif" "C:\Users\pawel\Downloads\ras250_gb\ras250_gb\data\NA.tif" "C:\Users\pawel\Downloads\ras250_gb\ras250_gb\data\NB.tif" "C:\Users\pawel\Downloads\ras250_gb\ras250_gb\data\NC.tif" "C:\Users\pawel\Downloads\ras250_gb\ras250_gb\data\ND.tif""   # Source GeoTIFF File(s) or URL(s)
- DestDataset_POSTGIS_RASTER = cw7   # Connection

Readers:
- SHAPEFILE_1: SHAPEFILE from $(SourceDataset_SHAPEFILE)
- GEOTIFF_1: GEOTIFF from $(SourceDataset_GEOTIFF)

Writers:
- POSTGIS_RASTER_1: POSTGIS_RASTER to $(DestDataset_POSTGIS_RASTER)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = TEST
    PASSED -> Aggregator
Aggregator
    ACCUM_ATTRS_NAME = Use Attributes From One Feature
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> scotland_and_wales_region (writer POSTGIS_RASTER_1)
    -> GEOTIFF (writer POSTGIS_RASTER_1)
scotland_and_wales_region (writer POSTGIS_RASTER_1)
    attributes: name varchar(100), area_code varchar(3), descriptio varchar(50), file_name varchar(100), number int8, number0 int8, polygon_id int8, unit_id int8, code varchar(9), hectares float4, area float4, type_code varchar(2), descript0 varchar(25), type_cod0 varchar(3), descript1 varchar(36)
GEOTIFF (writer POSTGIS_RASTER_1)
